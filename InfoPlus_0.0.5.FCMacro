# -*- coding: utf-8 -*-
# (c) 18Turbo, 2022

__Name__ = 'InfoPlus'
__Comment__ = 'Show details information'
__Author__ = '18Turbo (Rafael Martínez)'
__Version__ = '0.0.5'
__Date__ = '2022-08-22'
__License__ = 'LGPL-2.0-or-later'
__Web__ = 'https://github.com/18turbo/infoPlusFreeCAD'
__Wiki__ = ''
__Icon__ = 'https://github.com/18turbo/infoPlusFreeCAD/blob/main/infoplus.svg'
__Help__ = ''
__Status__ = 'beta'
__Requires__ = 'FreeCAD >= v0.20'
__Contact__ = 'https://github.com/18turbo'
__Communication__ = 'https://github.com/18turbo/infoPlusFreeCAD/issues'
__Files__ = 'infoplus.svg,infoPlus/infoPlus.ui'


# (En español:)

# Autor:			18Turbo
# Fecha:		    22-08-2022
# Versión:		0.0.5 BETA
#	
# Funcionalidad:	Muestra datos detallados del objeto seleccionado
#
# Notas de versiones:
# v.0.0.5:        Mejora de la presentación de algunos datos
#                Implementación de la masa
#                Todos los textos seleccionables
#                Presentación de todos los vértices del objeto
#                Presentación de todas las aristas del objeto
# v.0.0.4:        Nuevos objetos para mostrar información, y más información
# v.0.0.3:        Otra pestaña de información, mejora de los datos
# v.0.0.2:        Mejora presentación de los datos
# v.0.0.1:		Información del Bounding Box, área, volumen, ubicación, longitud.
#
#

import FreeCAD
from PySide import QtCore, QtGui, QtUiTools

rutaMacro = FreeCAD.ParamGet("User parameter:BaseApp/Preferences/Macro")     
rutaUI = rutaMacro.GetString("MacroPath","") + "/infoPlus/infoPlus.ui"
rutaUI = rutaUI.replace("\\","/")

principio = "("
fin = ") "

class infoPlus:

    def __init__(self):
        self.form = FreeCADGui.PySideUic.loadUi(rutaUI)
        self.form.setWindowTitle(objetoSeleccion.Label)
        tipo = seleccion[0].TypeId

        #Ubicación        
        if ((tipo.find('Sketcher::')>-1) or (tipo.find('PartDesign')>-1) or (tipo.find('Part::')>-1) or (tipo.find('Image::ImagePlane') >-1)
                or (tipo.find('App::Part')>-1) ):
            self.form.tab.setEnabled(True)
            self.ubicacion()
            # Ubicación (Longitud)
            if (tipo.find('PartDesign::Plane')>-1):
                self.longitud()
        #Bounding Box
        if (tipo.find('Sketcher::')>-1) or (tipo.find('PartDesign')>-1) or (tipo.find('Part::')>-1):
            self.form.tab.setEnabled(True)
            self.boundbox()
        #Composición
        if (tipo.find('Sketcher::')>-1) or (tipo.find('PartDesign')>-1) or (tipo.find('Part::')>-1):
            self.form.tab.setEnabled(True)
            self.composicion()
        #Área y Volumen
        if (tipo.find('Sketcher::')>-1) or (tipo.find('PartDesign')>-1) or (tipo.find('Part::')>-1):
            self.form.tab.setEnabled(True)
            self.areaVolumen()
        #Masa
        if (tipo.find('PartDesign')>-1):
            self.form.tab.setEnabled(True)
            self.masa()
        #Centro de Masas
        if (tipo.find('Sketcher::')>-1) or (tipo.find('PartDesign')>-1):
            self.form.tab.setEnabled(True)
            self.centroMasas()
        #Centro de Gravedad
        if (tipo.find('Sketcher::')>-1) or (tipo.find('PartDesign')>-1):
            self.form.tab.setEnabled(True)
            self.centroGravedad()
        #Imagen
        if (tipo.find('Image::ImagePlane') >-1):
            self.form.tab.setEnabled(True)
            self.dimImagenes() 
        #Datos
        if ((tipo.find('Sketcher::')>-1) or (tipo.find('PartDesign')>-1) or (tipo.find('Part::')>-1) or (tipo.find('Image::ImagePlane') >-1)
                or (tipo.find('App::Part')>-1) ):
            self.form.tab.setEnabled(True)
            self.datos()      
     

    def boundbox(self):
        self.form.boundingbox.setEnabled(True)  
        xmin = objetoSeleccion.Shape.BoundBox.XMin
        xmax = objetoSeleccion.Shape.BoundBox.XMax
        xlen = objetoSeleccion.Shape.BoundBox.XLength
        self.form.minx.setText(principio + str(round(xmin,2)) + fin + str(xmin))
        self.form.maxx.setText(principio + str(round(xmax,2)) + fin + str(xmax))
        self.form.lonx.setText(principio + str(round(xlen,2)) + fin + str(xlen))
        ymin = objetoSeleccion.Shape.BoundBox.YMin
        ymax = objetoSeleccion.Shape.BoundBox.YMax
        ylen = objetoSeleccion.Shape.BoundBox.YLength
        self.form.miny.setText(principio + str(round(ymin,2)) + fin + str(ymin))
        self.form.maxy.setText(principio + str(round(ymax,2)) + fin + str(ymax))
        self.form.lony.setText(principio + str(round(ylen,2)) + fin + str(ylen))
        zmin = objetoSeleccion.Shape.BoundBox.ZMin
        zmax = objetoSeleccion.Shape.BoundBox.ZMax
        zlen = objetoSeleccion.Shape.BoundBox.ZLength
        self.form.minz.setText(principio + str(round(zmin,2)) + fin + str(zmin))
        self.form.maxz.setText(principio + str(round(zmax,2)) + fin + str(zmax))
        self.form.lonz.setText(principio + str(round(zlen,2)) + fin + str(zlen))
        centroBBx = objetoSeleccion.Shape.BoundBox.Center[0]
        centroBBy = objetoSeleccion.Shape.BoundBox.Center[1]
        centroBBz = objetoSeleccion.Shape.BoundBox.Center[2]
        self.form.centrox.setText(principio + str(round(centroBBx,2)) + fin + str(centroBBx))
        self.form.centroy.setText(principio + str(round(centroBBy,2)) + fin + str(centroBBy))
        self.form.centroz.setText(principio + str(round(centroBBz,2)) + fin + str(centroBBz))
        lonDiagonalBB = objetoSeleccion.Shape.BoundBox.DiagonalLength
        self.form.diabb.setText(principio + str(round(lonDiagonalBB,2)) + fin + str(lonDiagonalBB))

    def ubicacion(self):
        self.form.basicos.setEnabled(True)
        ubicacionX = objetoSeleccion.Placement.Base[0]
        ubicacionY = objetoSeleccion.Placement.Base[1]
        ubicacionZ = objetoSeleccion.Placement.Base[2]
        self.form.ubx.setText(principio + str(round(ubicacionX, 2)) + fin + str(ubicacionX))
        self.form.uby.setText(principio + str(round(ubicacionY, 2)) + fin + str(ubicacionY))
        self.form.ubz.setText(principio + str(round(ubicacionZ, 2)) + fin + str(ubicacionZ))
        self.form.lonBase.setText(str(objetoSeleccion.Placement.Base.Length))

    def longitud(self):
        self.form.basicos.setEnabled(True)
        self.form.longitud.setText(str(objetoSeleccion.Length))

    def areaVolumen(self):
        self.form.basicos.setEnabled(True)
        areaBas = objetoSeleccion.Shape.Area
        volumenBas = objetoSeleccion.Shape.Volume
        self.form.area.setText(principio + str(round(areaBas,2)) + fin + str(areaBas))
        self.form.volumen.setText(principio + str(round(volumenBas,2)) + fin + str(volumenBas))

    def centroMasas(self):
        self.form.basicos.setEnabled(True)
        cmX = objetoSeleccion.Shape.CenterOfMass[0]
        cmY = objetoSeleccion.Shape.CenterOfMass[1]
        cmZ = objetoSeleccion.Shape.CenterOfMass[2]
        self.form.cmx.setText(principio + str(round(cmX, 2)) + fin + str(cmX))
        self.form.cmy.setText(principio + str(round(cmY, 2)) + fin + str(cmY))
        self.form.cmz.setText(principio + str(round(cmZ, 2)) + fin + str(cmZ))

    def centroGravedad(self):
        self.form.basicos.setEnabled(True)
        cgX = objetoSeleccion.Shape.CenterOfGravity[0]
        cgY = objetoSeleccion.Shape.CenterOfGravity[1]
        cgZ = objetoSeleccion.Shape.CenterOfGravity[2]
        self.form.cgx.setText(principio + str(round(cgX, 2)) + fin + str(cgX))
        self.form.cgy.setText(principio + str(round(cgY, 2)) + fin + str(cgY))
        self.form.cgz.setText(principio + str(round(cgZ, 2)) + fin + str(cgZ))

    def dimImagenes(self):
        self.form.imagen.setEnabled(True)
        self.form.imagen.setFocusPolicy(QtCore.Qt.TabFocus)
        self.form.imagen.setFocus()
        imgX = objetoSeleccion.XSize
        imgY = objetoSeleccion.YSize
        self.form.imgx.setText(str(imgX))
        self.form.imgy.setText(str(imgY))

    def composicion(self):        
        self.form.composicion.setEnabled(True)
        self.listaVertices = objetoSeleccion.Shape.Vertexes
        self.form.vertices.setText(str(len(self.listaVertices)))
        listaEjes = objetoSeleccion.Shape.Edges
        self.form.ejes.setText(str(len(listaEjes)))
        listaAlambres = objetoSeleccion.Shape.Wires
        self.form.alambres.setText(str(len(listaAlambres)))
        listaCaras = objetoSeleccion.Shape.Faces
        self.form.caras.setText(str(len(listaCaras)))

        if (len(listaCaras)>0):
            self.form.tabCaras.setEnabled(False)  

        if (len(self.listaVertices)>0):
            self.form.tabComp.setEnabled(True)
            self.form.tabVertices.setEnabled(True)            
            contador = 0
            for vert in self.listaVertices:
                self.form.comboVertices.addItem("Vértice " + str(contador) + ": (" +
                    str(round(self.listaVertices[contador].X,2)) + ", " + 
                    str(round(self.listaVertices[contador].Y,2)) + ", " +
                    str(round(self.listaVertices[contador].Z,2)) + ")" )         
                contador += 1
          
        if (len(listaEjes)>0):
            self.form.tabComp.setEnabled(True)
            self.form.tabEjes.setEnabled(True)            
            contador = 0
            for eje in listaEjes:
                vertice1 = eje.Vertexes[0].Point
                vertice2 = eje.Vertexes[-1].Point
                texto = "Arista " + str(contador) + ": v1 ("
                texto += str(round(vertice1[0],2)) + ", "
                texto += str(round(vertice1[1],2)) + ", "
                texto += str(round(vertice1[2],2)) + ")"
                texto += " | v2 ("
                texto += str(round(vertice2[0],2)) + ", "
                texto += str(round(vertice2[1],2)) + ", "
                texto += str(round(vertice2[2],2)) + ")"
                self.form.comboEjes.addItem(texto)
                texto2 = "Arista " + str(contador) + ": " + str(eje.Length) 
                self.form.comboEjesLongitudes.addItem(texto2)
                texto3 = "Arista " + str(contador) + ": " + str(eje.Mass)
                self.form.comboEjesMasas.addItem(texto3)
                contador += 1 

        listaSubformas = objetoSeleccion.Shape.SubShapes
        self.form.subformas.setText(str(len(listaSubformas)))
        listaCompuestos = objetoSeleccion.Shape.Compounds
        self.form.compuestos.setText(str(len(listaCompuestos)))
        listaFundas = objetoSeleccion.Shape.Shells
        self.form.fundas.setText(str(len(listaFundas)))
        listaSolidos = objetoSeleccion.Shape.Solids
        self.form.solidos.setText(str(len(listaSolidos)))

    def masa(self):
        self.form.basicos.setEnabled(True)
        mass = objetoSeleccion.Shape.Mass
        self.form.masa.setText(principio + str(round(mass,2)) + fin + str(mass))

    def datos(self):
        self.form.tabDatos.setEnabled(True)
        principioRojo = '<html><head/><body><p><span style=" color:#cc0000;">'
        principioAzul = '<html><head/><body><p><span style=" color:#0000cc;">'
        fin = '</span></p></body></html>'
        self.form.datoLabel.setText(principioRojo + objetoSeleccion.Label + fin)
        self.form.datoName.setText(objetoSeleccion.Name)
        self.form.datoFullName.setText(objetoSeleccion.FullName)
        self.form.datoLabel2.setText(objetoSeleccion.Label2)
        self.form.datoId.setText(principioAzul + str(objetoSeleccion.ID) + fin)
        visib = objetoSeleccion.Visibility
        if (visib):
            self.form.visibilidad.setText("Visible")
        else:
            self.form.visibilidad.setText("Oculto")


seleccion=Gui.Selection.getSelection()
if (len(seleccion) == 1):
    objetoSeleccion = App.ActiveDocument.getObject(seleccion[0].Name)
    infoPlus().form.show()
else:
    App.Console.PrintWarning("Debe seleccionar un solo objeto adecuado")
