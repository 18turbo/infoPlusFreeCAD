import FreeCAD
from PySide import QtCore, QtGui, QtUiTools

# Autor:			18Turbo
# Fecha:		16-08-2022
# Versión:		0.0.3 ALFA
#	
# Funcionalidad:	Muestra datos detallados del objeto seleccionado
#
# Notas de versiones:
# v.0.0.3:        Otra pestaña de información, mejora de los datos
# v.0.0.2:        Mejora presentación de los datos
# v.0.0.1:		Información del Bounding Box, área, volumen, ubicación, longitud.
#
#

rutaMacro = FreeCAD.ParamGet("User parameter:BaseApp/Preferences/Macro")     
rutaUI = rutaMacro.GetString("MacroPath","") + "/infoPlus/infoPlus.ui"
rutaUI = rutaUI.replace("\\","/")

principio = "("
fin = ") "

class infoPlus:

    def __init__(self):
        self.form = FreeCADGui.PySideUic.loadUi(rutaUI)
        self.form.setWindowTitle(objetoSeleccion.Label)
        self.form.tab.addTab(self.form.basicos,'Ubicación')
        self.form.tab.addTab(self.form.boundingbox,'BoundBox')
        self.form.tab.addTab(self.form.composicion,'Composición')
        tipo = seleccion[0].TypeId

        #Ubicación        
        if (tipo.find('Sketcher::')>-1) or (tipo.find('PartDesign')>-1) or (tipo.find('Part::')>-1):
            self.form.tab.setEnabled(True)
            self.ubicacion()
            # Ubicación (Longitud)
            if (tipo.find('PartDesign::Plane')>-1):
                self.longitud()

        #Bounding Box
        if (tipo.find('Sketcher::')>-1) or (tipo.find('PartDesign')>-1) or (tipo.find('Part::')>-1):
            self.form.tab.setEnabled(True)
            self.boundbox()

        #Composición
        if (tipo.find('Sketcher::')>-1) or (tipo.find('PartDesign')>-1) or (tipo.find('Part::')>-1):
            self.form.tab.setEnabled(True)
            self.composicion()
            

    def boundbox(self):
        self.form.boundingbox.setEnabled(True)  
        xmin = objetoSeleccion.Shape.BoundBox.XMin
        xmax = objetoSeleccion.Shape.BoundBox.XMax
        xlen = objetoSeleccion.Shape.BoundBox.XLength
        self.form.minx.setText(principio + str(round(xmin,2)) + fin + str(xmin))
        self.form.maxx.setText(principio + str(round(xmax,2)) + fin + str(xmax))
        self.form.lonx.setText(principio + str(round(xlen,2)) + fin + str(xlen))
        ymin = objetoSeleccion.Shape.BoundBox.YMin
        ymax = objetoSeleccion.Shape.BoundBox.YMax
        ylen = objetoSeleccion.Shape.BoundBox.YLength
        self.form.miny.setText(principio + str(round(ymin,2)) + fin + str(ymin))
        self.form.maxy.setText(principio + str(round(ymax,2)) + fin + str(ymax))
        self.form.lony.setText(principio + str(round(ylen,2)) + fin + str(ylen))
        zmin = objetoSeleccion.Shape.BoundBox.ZMin
        zmax = objetoSeleccion.Shape.BoundBox.ZMax
        zlen = objetoSeleccion.Shape.BoundBox.ZLength
        self.form.minz.setText(principio + str(round(zmin,2)) + fin + str(zmin))
        self.form.maxz.setText(principio + str(round(zmax,2)) + fin + str(zmax))
        self.form.lonz.setText(principio + str(round(zlen,2)) + fin + str(zlen))
        centroBBx = objetoSeleccion.Shape.BoundBox.Center[0]
        centroBBy = objetoSeleccion.Shape.BoundBox.Center[1]
        centroBBz = objetoSeleccion.Shape.BoundBox.Center[2]
        self.form.centrox.setText(principio + str(round(centroBBx,2)) + fin + str(centroBBx))
        self.form.centroy.setText(principio + str(round(centroBBy,2)) + fin + str(centroBBy))
        self.form.centroz.setText(principio + str(round(centroBBz,2)) + fin + str(centroBBz))
        lonDiagonalBB = objetoSeleccion.Shape.BoundBox.DiagonalLength
        self.form.diabb.setText(principio + str(round(lonDiagonalBB,2)) + fin + str(lonDiagonalBB))

    def ubicacion(self):
        self.form.basicos.setEnabled(True)
        self.form.area.setText(str(objetoSeleccion.Shape.Area))
        self.form.volumen.setText(str(objetoSeleccion.Shape.Volume))
        ubicacionX = objetoSeleccion.Placement.Base[0]
        ubicacionY = objetoSeleccion.Placement.Base[1]
        ubicacionZ = objetoSeleccion.Placement.Base[2]
        self.form.ubx.setText(principio + str(round(ubicacionX, 2)) + fin + str(ubicacionX))
        self.form.uby.setText(principio + str(round(ubicacionY, 2)) + fin + str(ubicacionY))
        self.form.ubz.setText(principio + str(round(ubicacionZ, 2)) + fin + str(ubicacionZ))
        self.form.lonBase.setText(str(objetoSeleccion.Placement.Base.Length))
        cmX = objetoSeleccion.Shape.CenterOfMass[0]
        cmY = objetoSeleccion.Shape.CenterOfMass[1]
        cmZ = objetoSeleccion.Shape.CenterOfMass[2]
        self.form.cmx.setText(principio + str(round(cmX, 2)) + fin + str(cmX))
        self.form.cmy.setText(principio + str(round(cmY, 2)) + fin + str(cmY))
        self.form.cmz.setText(principio + str(round(cmZ, 2)) + fin + str(cmZ))
        cgX = objetoSeleccion.Shape.CenterOfGravity[0]
        cgY = objetoSeleccion.Shape.CenterOfGravity[1]
        cgZ = objetoSeleccion.Shape.CenterOfGravity[2]
        self.form.cgx.setText(principio + str(round(cgX, 2)) + fin + str(cgX))
        self.form.cgy.setText(principio + str(round(cgY, 2)) + fin + str(cgY))
        self.form.cgz.setText(principio + str(round(cgZ, 2)) + fin + str(cgZ))

    def longitud(self):
        self.form.basicos.setEnabled(True)
        self.form.longitud.setText(str(objetoSeleccion.Length))

    def composicion(self):
        self.form.composicion.setEnabled(True)
        listaVertices = objetoSeleccion.Shape.Vertexes
        self.form.vertices.setText(str(len(listaVertices)))
        listaEjes = objetoSeleccion.Shape.Edges
        self.form.ejes.setText(str(len(listaEjes)))
        listaCaras = objetoSeleccion.Shape.Faces
        self.form.caras.setText(str(len(listaCaras)))
        listaSubformas = objetoSeleccion.Shape.SubShapes
        self.form.subformas.setText(str(len(listaSubformas)))
        listaCompuestos = objetoSeleccion.Shape.Compounds
        self.form.compuestos.setText(str(len(listaCompuestos)))
        listaFundas = objetoSeleccion.Shape.Shells
        self.form.fundas.setText(str(len(listaFundas)))
        listaSolidos = objetoSeleccion.Shape.Solids
        self.form.solidos.setText(str(len(listaSolidos)))


seleccion=Gui.Selection.getSelection()
if (len(seleccion) == 1):
    objetoSeleccion = App.ActiveDocument.getObject(seleccion[0].Name)
    infoPlus().form.show()
else:
    App.Console.PrintWarning("Debe seleccionar un solo objeto adecuado")
